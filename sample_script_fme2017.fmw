FME workspace sample_script_fme2017.fmw

Parameters:
- Perimeter = POLYGON((6.62109005603303 46.51536036165384,6.623120852165147 46.51549642732441,6.624988144606661 46.514808141964856,6.631069256716269 46.51335375210718,6.633663816944302 46.51500498298585,6.6346635513963355 46.5174410136014,6.634317903072555 46.51965159759916,6.630126770513636 46.520175062789534,6.624571816554757 46.52168716079147,6.621892888161173 46.52173537632152,6.621992478963257 46.52031920938455,6.617510362580848 46.51939624209985,6.617601866780929 46.518519785202706,6.6183731545887765 46.51793162269317,6.618552647567806 46.51640808253532,6.62109005603303 46.51536036165384))   # Polygone d'export (au format WKT) 
- Product = 6f5afa6b-7f0a-ec54-a9a7-44f004d6edda   # Identifiant du produit 
- FolderOut = C:\temp\_extract\output   # Répertoire de sortie 
- Parameters = {"FORMAT":"DXF","PROJECTION":"SWITZERLAND","SELECTION":"PASS_THROUGH","GROUPMENT":"YES","RAISON":"AVARIE","Communes":"","REMARK":"Parcelle N°3658 à Clarens \u0022Montreux\u0022"}   # Liste dynamique de paramètres au format json
- OrderLabel = 259546   # Libellé de la commande 
- Request = 365   # Identifiant de la requête 
- Client = 2edc1a50-4837-4c44-1519-3ebc85f14588   # Identifiant du client 
- Organism = 4a142a5d-16bf-84d4-111f-57d76c834493   # Identifiant de l'organisme 
- DestDataset_ACAD = $(FolderOut)/$(OrderLabel).dxf   # Destination Autodesk AutoCAD DWG/DXF File

Writers:
- ESRISHAPE_1: ESRISHAPE to $(FolderOut)
- FILEGDB_1: FILEGDB to $(FolderOut)
- ACAD_1: ACAD to $(DestDataset_ACAD)

Note: Output : OUTPUT [FILEGDB]
Products (writer FILEGDB_1)
Note: Output [ESRISHAPE]
Shapefile1 (writer ESRISHAPE_1)
Note: Output [ACAD]
Layer1 (writer ACAD_1)
    attributes: PROJECTION_EPSG char(200), PROJECTION_NOM char(200), FORMAT char(200)

Bookmark: Récupération des paramètres du workbench à partir de la liste générique de [Parameters] au format json
1_InitJSONforParameters: Creator
    GEOMTYPE = Geometry Object
    NUM = 1
    CREATED -> JSONFlattener
JSONFlattener
    PREFIX_STRING = json_
    RECURSIVE = Yes
    NEW_ATTRIBUTES = json_FORMAT json_SELECTION json_PROJECTION json_REMARK
    JSON_DOCUMENT = $(Parameters)
    ERROR_LIST_ATTR = _json_error
    -> Parameter_FORMAT
Parameter_FORMAT: VariableSetter
    VALUE = @Value(json_FORMAT)
    SCOPE = Global
    VARNAME = FORMAT
    -> Parameter_SELECTION
Parameter_SELECTION: VariableSetter
    VALUE = @Value(json_SELECTION)
    SCOPE = Global
    VARNAME = SELECTION
    -> Parameter_PROJECTION_EPSG
Parameter_PROJECTION_EPSG: VariableSetter
    VALUE = FME_CONDITIONAL:DEFAULT_VALUE'@Abort(No valid projection defined)'BOOL_OP;OR;COMPOSITE_TEST;<Unused>;TEST @Value(json_PROJECTION) = SWITZERLAND'EPSG:21781'BOOL_OP;OR;COMPOSITE_TEST;<Unused>;TEST @Value(json_PROJECTION) = SWITZERLAND95'EPSG:2056'FME_NUM_CONDITIONS3___
    SCOPE = Global
    VARNAME = PROJECTION_EPSG
    -> Parameter_PROJECTION_NOM
Parameter_PROJECTION_NOM: VariableSetter
    VALUE = FME_CONDITIONAL:DEFAULT_VALUE'@Abort(No valid projection defined)'BOOL_OP;OR;COMPOSITE_TEST;<Unused>;TEST @Value(json_PROJECTION) = SWITZERLAND'MN03'BOOL_OP;OR;COMPOSITE_TEST;<Unused>;TEST @Value(json_PROJECTION) = SWITZERLAND95'MN95'FME_NUM_CONDITIONS3___
    SCOPE = Global
    VARNAME = PROJECTION_NOM
    -> Parameter_json_REMARK
Parameter_json_REMARK: VariableSetter
    VALUE = @Value(json_REMARK)
    SCOPE = Global
    VARNAME = REMARK
    -> Parameter_REMARK
Parameter_REMARK: VariableRetriever
    SCOPE = Global
    VALUE_ATTR = REMARK
    VARNAME = REMARK
    -> GeometryReplacer

Bookmark: Génération du périmètre d'export à partir de [Perimeter] en format WKT
GeometryReplacer
    SOURCE = $(Perimeter)
    REMOVE_ATTRIBUTE = Yes
    KIND_LONG = OGC Well Known Text
    OGC_WKT_PRECISION_DISPLAY = 64-bit
    -> FeatureReader_2 [INITIATOR]

Bookmark: Extraction avec le pérmiètre de commande
FeatureReader_2
    FORMAT = ESRISHAPE
    ESRISHAPE_SIMPLE_DONUT_GEOMETRY = simple
    ESRISHAPE_MEASURES_AS_Z = no
    ESRISHAPE_DISSOLVE_HOLES = no
    INTERACT = Intersects
    ESRISHAPE_UPPER_CASE_ATTR_NAMES = No
    ESRISHAPE_TRIM_PRECEDING_SPACES = yes
    ATTR_ACCUM_MODE = Only Use Result
    ESRISHAPE_CHECK_NUMERIC_FIELDS = yes
    ESRISHAPE_USE_SEARCH_ENVELOPE = NO
    ESRISHAPE_REPORT_BAD_GEOMETRY = no
    DATASET = $(FME_MF_DIR_ENCODED)data\osm-geofabrik\*.shp
    COMBINE_GEOM = Use Result
    OUTPUT_FEATURES_DISPLAY = Schema and Data Features
    <SCHEMA> -> Products (writer FILEGDB_1)
    <SCHEMA> -> Shapefile1 (writer ESRISHAPE_1)
    <OTHER> -> VariableRetriever_PROJECTION_EPSG

Bookmark: Transformations utilisant les paramètres récupérés précédemment
VariableRetriever_PROJECTION_EPSG
    SCOPE = Global
    VALUE_ATTR = PROJECTION_EPSG
    VARNAME = PROJECTION_EPSG
    -> VariableRetriever_PROJECTION_NOM
VariableRetriever_PROJECTION_NOM
    SCOPE = Global
    VALUE_ATTR = PROJECTION_NOM
    VARNAME = PROJECTION_NOM
    -> VariableRetriever_FORMAT
VariableRetriever_FORMAT
    SCOPE = Global
    VALUE_ATTR = FORMAT
    VARNAME = FORMAT
    -> Reprojector
Reprojector
    INTERPOLATION_TYPE_NAME = Nearest Neighbor
    RASTER_CELL_SIZE = Preserve Cells
    SOURCE = Read from feature
    DEST = @Value(PROJECTION_EPSG)
    REPROJECTED -> AttributeFilter
AttributeFilter
    ATTR_NAME = FORMAT
    ATTR_VALUES = <Empty>,<Missing>,<Null>,<Unfiltered>,GDB,SHP,DXF,DWG
    GDB -> GeometryFilter
    SHP -> Shapefile1 (writer ESRISHAPE_1)
    DXF -> Layer1 (writer ACAD_1)
    DWG -> Layer1 (writer ACAD_1)

Bookmark: Cas des multipoints
GeometryFilter
    BREAK_AGG = No
    GEOM_PORT_NAMES = Point
    POINT -> Deaggregator
    <UNFILTERED> -> Products (writer FILEGDB_1)
Deaggregator
    PART_NUMBER_FIELD = _part_number
    GEOM_NAME_FIELD = _geometry_name
    SPLIT_COMPOSITES = No
    EXPLODE_INSTANCES = No
    LIST_ATTR_MODE_LOOKUP = LEAN
    MODE = Flatten One Level
    DEAGGREGATED -> Products (writer FILEGDB_1)
